DAECGE-BRIGHTC-MIB DEFINITIONS ::= BEGIN

IMPORTS
    MODULE-IDENTITY, OBJECT-TYPE, NOTIFICATION-TYPE,
    enterprises, Integer32, Counter32, Gauge32
        FROM SNMPv2-SMI
    DisplayString
        FROM SNMPv2-TC;

brightcMIB MODULE-IDENTITY
    LAST-UPDATED "202607300000Z"
    ORGANIZATION "StructCore Embedded"
    CONTACT-INFO "support@structcore.com"
    DESCRIPTION
        "MIB for relay control, sensor readings, and events for the BrightC-B1 V3 firmware."
    REVISION     "202607300000Z"
    DESCRIPTION  "Initial version of the private BrightC MIB."
    ::= { enterprises 3134 }

-- Main Groups
brightcObjects      OBJECT IDENTIFIER ::= { brightcMIB 1 }
brightcTraps        OBJECT IDENTIFIER ::= { brightcMIB 2 }

-- Object Subgroups
brightcControl      OBJECT IDENTIFIER ::= { brightcObjects 1 }
brightcSensors      OBJECT IDENTIFIER ::= { brightcObjects 2 }
brightcStats        OBJECT IDENTIFIER ::= { brightcObjects 3 }

-------------------------------------------------------------------------------
-- Control Group (Read-Write)
-------------------------------------------------------------------------------

relayAA1State OBJECT-TYPE
    SYNTAX      INTEGER { off(0), on(1) }
    MAX-ACCESS  read-write
    STATUS      current
    DESCRIPTION
        "Status of the Main Relay AA1 (0 = Off/Open, 1 = On/Closed)."
    ::= { brightcControl 1 }

alarmOut1State OBJECT-TYPE
    SYNTAX      INTEGER { off(0), on(1) }
    MAX-ACCESS  read-write
    STATUS      current
    DESCRIPTION
        "Status of Alarm Output ALM_OUT_1 (0 = Inactive, 1 = Active)."
    ::= { brightcControl 2 }

buzzerState OBJECT-TYPE
    SYNTAX      INTEGER { off(0), on(1) }
    MAX-ACCESS  read-write
    STATUS      current
    DESCRIPTION
        "Status of the PWM Buzzer (0 = Silent, 1 = Beep Active)."
    ::= { brightcControl 3 }

-------------------------------------------------------------------------------
-- Sensor Group (Read-Only)
-------------------------------------------------------------------------------

tempSensorCh1 OBJECT-TYPE
    SYNTAX      Gauge32
    MAX-ACCESS  read-only
    STATUS      current
    DESCRIPTION
        "Current temperature sensor CH1 reading (degrees Celsius * 10)."
    ::= { brightcSensors 1 }

pressureSensorCh1 OBJECT-TYPE
    SYNTAX      Gauge32
    MAX-ACCESS  read-only
    STATUS      current
    DESCRIPTION
        "Current pressure sensor CH1 reading in PSI."
    ::= { brightcSensors 2 }

-------------------------------------------------------------------------------
-- Statistics Group (Read-Only)
-------------------------------------------------------------------------------

uptimeSeconds OBJECT-TYPE
    SYNTAX      Counter32
    MAX-ACCESS  read-only
    STATUS      current
    DESCRIPTION
        "Total elapsed seconds since device power-on."
    ::= { brightcStats 1 }

-------------------------------------------------------------------------------
-- Notifications and Traps
-------------------------------------------------------------------------------

alarmEventTrap NOTIFICATION-TYPE
    OBJECTS     { alarmOut1State, tempSensorCh1 }
    STATUS      current
    DESCRIPTION
        "Notification emitted when an alarm is triggered or exceeds thresholds."
    ::= { brightcTraps 1 }

END
